module ietf-i2rs-rib {
  namespace "urn:ietf:params:xml:ns:yang:ietf-i2rs-rib";
  // replace with iana namespace when assigned
  prefix "iir";

  import ietf-inet-types {
    prefix inet;
    //rfc6991
  }

  organization
    "IETF I2RS (Interface to Routing System) Working Group";
  contact
     "Editor:   Daniel Fomin
               <mailto:daniel.fomin@mytum.de>";
  description
    "This module defines a YANG data model for
     Routing Information Base (RIB) that aligns
     with the I2RS RIB information model.";
  revision "2018-12-05" {
    description "initial revision";
    reference "draft-ietf-i2rs-data-model-09";
  }


container routing-instance {
    description
      "A routing instance, in the context of
       the RIB information model, is a collection
       of RIBs, interfaces, and routing parameters";
 list route-list {
        key "route-index";
        description
          "A list of routes of a rib.";
      leaf route-index {
	             type uint64 ;
	             mandatory true;
	             description
	              "Route index.";
	}	

	container route {
	description
	  "A single routing entry";
	

	leaf prefix {
                     type inet:ipv4-prefix;
                     mandatory true;
                     description
                      "An IPv4 destination address as the match.";
                    }
        leaf nexthop {
                     type inet:ipv4-address;
                     mandatory true;
                     description
                     "The nexthop is an IPv4 address.";
                }
        leaf route-preference {
                     type uint32;
                     mandatory true;
                     description
                     "The preference of the route";
        }
	}
      }


}


    grouping route-operation-state {
      description "Route operation state.";
      leaf success-count {
        type uint32;
        mandatory true;
        description
          "The numbers of routes that are successfully
         added/deleted/updated.";
      }

      leaf failed-count {
        type uint32;
        mandatory true;
        description
          "The numbers of the routes that are failed
         to be added/deleted/updated.";
      }

      container failure-detail {
        description
          "The failure detail reflects the reason why a route
         operation fails. It is a array that includes the route
         index and error code of the failed route.";
        list failed-routes {
          key "route-index";
          description
            "The list of failed routes.";
          leaf route-index {
            type uint32;
            description
              "The route index of the failed route.";
          }

          leaf error-code {
            type uint32;
            description
              "The error code that reflects the failure reason.";
          }
        }  // list failed-routes
      }  // container failure-detail
    }  // grouping route-operation-state

  rpc route-add {
    description
      "To add a route or a list of route to a rib";
    input {
      leaf return-failure-detail {
        type boolean;
        default false;
        description
          "Whether return the failure detail.
           true  - return the failure detail;
           false - do not return the failure detail;
           the default is false.";
      }

	 leaf prefix {
			  type inet:ipv4-prefix;
			  mandatory true;
			  description
			    "An IPv4 destination address as the match.";
			}
	leaf nexthop {
		  type inet:ipv4-address;
		  mandatory true;
		  description
		    "The nexthop is an IPv4 address.";
		}
	leaf route-preference {
	      type uint32;
	      mandatory true;
	      description
		"The preference of the route";
	}




    }
    output {
      uses route-operation-state;
    }
  }
  rpc route-delete {
    description
      "To delete a route";
    input {
      leaf return-failure-detail {
        type boolean;
        default false;
        description
          "Whether return the failure detail.
           true  - return the failure detail;
           false - do not return the failure detail;
           the default is false.";
      }

	 leaf prefix {
			  type inet:ipv4-prefix;
			  mandatory true;
			  description
			    "An IPv4 destination address as the match.";
			}
	leaf nexthop {
		  type inet:ipv4-address;
		  mandatory true;
		  description
		    "The nexthop is an IPv4 address.";
		}
	leaf route-preference {
	      type uint32;
	      mandatory true;
	      description
		"The preference of the route";
	}




    }
    output {
      uses route-operation-state;
    }
  }
}
